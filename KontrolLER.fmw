FME workspace KontrolLER.fmw
Title: KontrolLER
History: 2026-01-09,bw5z,Rapporten flyttes til KGB for at kunne håndtere flere datamodeller,2026-06-09,bw5z,Tilføjet buffer til BBOX,2026-08-26,bw5z,Stardværdi for existingFromDB sat til Ja,2026-08-31,bw5z,Fejlhåndtering af NULL-geometrier på buffer

Parameters:
- title =   # Titel
- existingFromDB = 1   # Inkludér Københavns Kommunes eksisterende ledningsoplysninger
- inputFile =   # "" Upload ledningsoplysninger til kontrol
- kontrolSchema = ler
- FME_SERVER_DEST_DIR = $(FME_SHAREDRESOURCE_DATA)\LER   # FME Flow Destination Directory
- FME_SHAREDRESOURCE_DATA = $(FME_MF_DIR)testdata   # FME Flow Data Directory

Writers:
- HTML_1: HTML to $(FME_WORKSPACE_DIR)\KontrolLER.html

Bookmark: Håndtering af relevante inputfiler, evt. uden data
SQLCreator
    DATASET = KGBPRODSU
    EXPOSED_ATTRIBUTE_LIST = input_file_type_lw,_primary
    FORMAT = POSTGRES
    OUTPUT_FEATURES_DISPLAY = Schema and Data Features
    POSTGRES_CREATE_FEATURE_TABLES_FROM_DATA = Yes
    POSTGRES_NAMED_CONNECTION = KGBPRODSU
    POSTGRES_QUERY_FEATURE_TYPES_FOR_MERGE_FILTERS = Yes
    POSTGRES_READ_TIME_WITH_TIMEZONE = Yes
    SQL_STATEMENT:
      SELECT
          LOWER(u.navn) AS input_file_type_lw
      	,(LOWER(f.navn) = LOWER(u.navn))::int AS _primary
      FROM $(kontrolSchema).kontrol_fme_filtyper f
          ,UNNEST(navn_lst) u(navn)
    RESULT -> FeatureMerger_2 [SUPPLIER]
FeatureMerger_2
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = @Value(input_file_type_lw) @Value(input_file_type_lw) AUTO
    MERGE_TYPE = Attributes Only
    PROCESS_DUPS = YES
    REJECT_NULL_MISSING_KEYS = No
    SUPPLIERS_FIRST = No
    MERGED -> Tester_2
    UNMERGED_REQUESTOR -> AttributeCreator_3
Note: Diverse extensionfiler fjernes
Tester_2
    BOOL_OP = OR
    TEST_CLAUSE = TEST @Value(_primary) = 1
    TEST_MODE = TEST
    PASSED -> Tester_3
Note: Håndtér Geopackage separat
Tester_3
    BOOL_OP = OR
    TEST_CLAUSE = TEST @Value(input_file_type_lw) = gpkg
    TEST_MODE = TEST
    PASSED -> SQLExecutor [INITIATOR]
    FAILED -> AttributeCreator_3
SQLExecutor
    ATTR_IGNORE_NULLS = No
    COMBINE_ATTRS = Keep Result Attributes if Conflict
    COMBINE_GEOM = Initiator Geometry Only
    DATASET = @Value(input_file_full_path_lw)
    EXPOSED_ATTRIBUTE_LIST = table_name
    FORMAT = OGCGEOPACKAGE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OUTPUT_FEATURES_DISPLAY = Data Features
    SQL_STATEMENT:
      SELECT
          table_name
      FROM gpkg_contents
      WHERE data_type = 'features'
    RESULT -> FeatureJoiner_2 [LEFT]
    INITIATOR -> FeatureJoiner_2 [RIGHT]
FeatureJoiner_2
    ATTR_CONFLICT_RES = Prefer Left
    GEOMETRY_HANDLING = Prefer Left
    JOIN_KEYS = input_file_full_path input_file_full_path AUTO
    JOIN_MODE = Inner
    JOINED -> AttributeCreator_3
    UNJOINED_RIGHT -> AttributeCreator_3
AttributeCreator_3
    ATTR_TABLE:
      SET_TO fme_feature_type (varchar(200)) = FME_CONDITIONAL:DEFAULT_VALUE'@Value(input_file_name)'BOOL_OP;AND;COMPOSITE_TEST;1;TEST @LowerCase(@Value(input_file_type)) = gpkg'@Value(table_name)'FME_NUM_CONDITIONS2___
      SET_TO fme_feature_type_name (varchar(200)) = @Value(fme_feature_type):@Value(input_file_name):@Value(input_file_type)
      SET_TO feature_type_format (buffer) = featureType:fileName:fileExtension
    -> FeatureMerger [REQUESTOR]

Bookmark: Visse attributter filtreres fra
SQLCreator_2
    DATASET = KGBPRODSU
    EXPOSED_ATTRIBUTE_LIST = navn
    FORMAT = POSTGRES
    OUTPUT_FEATURES_DISPLAY = Schema and Data Features
    POSTGRES_CREATE_FEATURE_TABLES_FROM_DATA = Yes
    POSTGRES_NAMED_CONNECTION = KGBPRODSU
    POSTGRES_QUERY_FEATURE_TYPES_FOR_MERGE_FILTERS = Yes
    POSTGRES_READ_TIME_WITH_TIMEZONE = Yes
    SQL_STATEMENT:
      SELECT
          navn
      FROM $(kontrolSchema).kontrol_fme_attributter_exclude
      WHERE aktiv IS TRUE
    RESULT -> FeatureMerger_5 [SUPPLIER]
AttributeKeeper
    CREATE_BULK_MODE_FEATURES = NO
    KEEP_ATTRS = fme_feature_type_name
    KEEP_LIST = attribute{}
    -> CoordinateSystemExtractor
CoordinateSystemExtractor
    CRDSYS_ATTR = coordsys
    -> CoordinateSystemEPSG
CoordinateSystemEPSG: CoordinateSystemDescriptionConverter
    DIRECTION_LONG = Convert From FME Representation
    KIND_LONG = EPSG Number
    SRC = coordsys
    VAL_ATTR = coordsys_epsg
    -> CoordinateSystemRemover_2
    -> Junction_2
Junction_2
    -> FeatureMerger_6 [SUPPLIER]
CoordinateSystemRemover_2
    -> ListExploder_2
ListExploder_2
    ATTR_ACCUM_MODE = Merge List Attributes
    ATTR_CONFLICT_RES = Use List Attribute Values
    INDEX_ATTR = _element_index
    LIST_ATTR = attribute{}
    ELEMENTS -> Tester
Tester
    BOOL_OP = COMPOSITE
    COMPOSITE_TEST = NOT ( 1 OR 2 OR 3 OR 4 )
    TEST_CLAUSE:
      CASE_INSENSITIVE_TEST @Value(name) BEGINS_WITH input_
      CASE_INSENSITIVE_TEST @Value(name) BEGINS_WITH fme_
      CASE_INSENSITIVE_TEST @Value(name) BEGINS_WITH shapefile_
      CASE_INSENSITIVE_TEST @Value(name) BEGINS_WITH geopackage_
    TEST_MODE = PER_TEST
    PASSED -> FeatureMerger_5 [REQUESTOR]
FeatureMerger_5
    ATTR_ACCUM_MODE = Merge Supplier
    ATTR_CONFLICT_RES = Use Requestor
    IGNORE_NULLS = No
    JOIN_KEYS = @LowerCase(@Value(name)) @Value(navn) AUTO
    MERGE_TYPE = Attributes Only
    PROCESS_DUPS = NO
    REJECT_NULL_MISSING_KEYS = No
    SUPPLIERS_FIRST = No
    UNMERGED_REQUESTOR -> Sorter_3
    UNMERGED_REQUESTOR -> FeatureJoiner [RIGHT]

Bookmark: Data fra inputfiler hentes
Note: START
Creator
    GEOMTYPE = Geometry Object
    NUM = 1
    CREATED -> AttributeCreator
AttributeCreator
    ATTR_TABLE:
      SET_TO input_file (varchar(200)) = $(inputFile)
      SET_TO input_file (varchar(200)) = @ReplaceString(@Value(input_file),"\" \"","|||")
      SET_TO input_file (varchar(200)) = @ReplaceString(@Value(input_file),"""","")
    -> AttributeSplitter
AttributeSplitter
    ATTR_NAME = input_file
    DELIMITER = |||
    DROP_EMPTY_PARTS = No
    LIST_NAME = input_file
    TRIM_OPTION = Both
    -> ListExploder
ListExploder
    ATTR_ACCUM_MODE = Merge List Attributes
    ATTR_CONFLICT_RES = Use List Attribute Values
    LIST_ATTR = input_file{}
    ELEMENTS -> AttributeCreator_2
AttributeCreator_2
    ATTR_TABLE:
      SET_TO input_file_full_path (varchar(200)) = @Value(input_file)
      SET_TO input_file (varchar(200)) = @ReplaceRegularExpression(@Value(input_file),"^.+[/\\](.+)$",\1)
      SET_TO input_file_name (varchar(200)) = @ReplaceRegularExpression(@Value(input_file),^(.+)\..+?$,\1)
      SET_TO input_file_type (varchar(200)) = FME_CONDITIONAL:DEFAULT_VALUE'FME_NULL_VALUE'BOOL_OP;OR;COMPOSITE_TEST;1;CASE_INSENSITIVE_TEST @Value(input_file) CONTAINS .'@ReplaceRegularExpression(@Value(input_file),^.+\.,"")'FME_NUM_CONDITIONS2___
      SET_TO input_file_full_path_lw (varchar(200)) = @LowerCase(@Value(input_file_full_path))
      SET_TO input_file_lw (varchar(200)) = @LowerCase(@Value(input_file))
      SET_TO input_file_name_lw (varchar(200)) = @LowerCase(@Value(input_file_name))
      SET_TO input_file_type_lw (varchar(200)) = FME_CONDITIONAL:DEFAULT_VALUE'FME_NULL_VALUE'BOOL_OP;OR;COMPOSITE_TEST;1;TEST input_file_type ATTRIBUTE_HAS_A_VALUE _FME_BLANK_STRING_'@LowerCase(@Value(input_file_type))'FME_NUM_CONDITIONS2___
    -> TestFilter
    -> Junction
TestFilter
    DEFAULT_VALUE = <UNFILTERED>
    PASSED_TEST_GROUP_OUTPUT = FIRST
    TEST_LIST = "BOOL_OP,OR,COMPOSITE_TEST,""""""1"""""",TEST_CLAUSE,TEST @Value(input_file_type_lw) = gpkg",GPKG,"BOOL_OP,OR,COMPOSITE_TEST,""""""1"""""",TEST_CLAUSE,TEST @Value(input_file_type_lw) = shp",SHP
    GPKG -> FeatureReaderGPKG [INITIATOR]
    SHP -> FeatureReaderSHP [INITIATOR]
FeatureReaderSHP
    ATTRS_TO_EXPOSE = fme_feature_type
    ATTR_ACCUM_MODE = Merge Initiator and Result
    ATTR_CONFLICT_RES = Use Result
    ATTR_IGNORE_NULLS = No
    COMBINE_GEOM = Use Result
    DATASET = @Value(input_file_full_path_lw)
    FORMAT = SHAPEFILE
    INTERACT = NONE
    ORDER_RESULTS = No
    OUTPUT_FEATURES_DISPLAY = Data Features
    SHAPEFILE_DONUT_DETECTION = ORIENTATION
    SHAPEFILE_ENCODING = fme-source-encoding
    SHAPEFILE_MEASURES_AS_Z = No
    SHAPEFILE_NUMERIC_TYPE_ATTRIBUTE_HANDLING = STANDARD_TYPES
    SHAPEFILE_READ_BLANK_AS = NULL
    SHAPEFILE_READ_NUMERIC_PADDING_AS = BLANK
    SHAPEFILE_REPORT_BAD_GEOMETRY = No
    SHAPEFILE_TRIM_PRECEDING_SPACES = Yes
    SHAPEFILE_USE_SEARCH_ENVELOPE = NO
    SHAPEFILE_USE_STRING_FOR_NUMERIC_STORAGE = No
    <OTHER> -> Junction_4
FeatureReaderGPKG
    ATTRS_TO_EXPOSE = fme_feature_type fme_type
    ATTR_ACCUM_MODE = Merge Initiator and Result
    ATTR_CONFLICT_RES = Use Result
    ATTR_IGNORE_NULLS = No
    COMBINE_GEOM = Use Result
    DATASET = @Value(input_file_full_path_lw)
    FORMAT = OGCGEOPACKAGE
    INTERACT = NONE
    OGCGEOPACKAGE_ENCODE_FEATURE_TYPE_AND_ATTR_NAMES = YES
    OGCGEOPACKAGE_ENFORCE_FOREIGN_KEY_INTEGRITY = YES
    OGCGEOPACKAGE_EXPOSE_PRIMARY_KEY_ATTRIBUTE = YES
    OGCGEOPACKAGE_OGCGEOPACKAGE_EXPOSE_FORMAT_ATTRS = fme_basename,text(50) fme_feature_type,text(50)
    OGCGEOPACKAGE_OPEN_SINGLE_RASTER_AS_SUBDATASET = YES
    OGCGEOPACKAGE_QUERY_FEATURE_TYPES_FOR_MERGE_FILTERS = Yes
    OGCGEOPACKAGE_READER_REPLACE_INVALID_CHARS = YES
    OGCGEOPACKAGE_READ_BOOLEANS_AS_YES_NO = YES
    OGCGEOPACKAGE_READ_NULLS = YES
    OGCGEOPACKAGE_USE_SEARCH_ENVELOPE = NO
    ORDER_RESULTS = No
    OUTPUT_FEATURES_DISPLAY = Data Features
    <OTHER> -> Junction_4
Junction_4
    -> SchemaScanner
Junction
    -> FeatureMerger_2 [REQUESTOR]

Bookmark: Inputdata forberedes og skemaer genereres
SchemaScanner
    CASE = No
    EMPTY_ATTR_HANDLING = SCANNER_DEFAULT
    GROUP_BY = fme_feature_type input_file_name input_file_type
    HOLD = Yes
    NUMERIC_ALLOW_LEADING_ZEROES = Yes
    SCHEMA_NAME_ATTR = fme_feature_type_name
    UNBOUNDED_NUMBERS = Yes
    UNBOUNDED_STRINGS = Yes
    -> Counter_ID
    <SCHEMA> -> Junction_5
Counter_ID
    CNT_ATTR = feature_id
    GROUP_BY = fme_feature_type_name
    SCOPE = Local
    START = 1
    -> GeometryFilter
GeometryFilter
    FILTER_MODE = SIMPLE
    FILTER_MULTI = FILTER_TYPES]Null]FME_CONTROLLER_QUERY_FILE]]FME_CONTROLLER_CHOICE]Simple
    Null -> CoordinateSystemRemover
    <UNFILTERED> -> GeometryExtractor
GeometryExtractor
    ATTR = geometry_wkt
    KIND_LONG = OGC Well Known Text
    OGCVERSION = 1.2
    OGC_WKT_PRECISION_DISPLAY = 64-bit
    REMOVE_GEOMETRY = No
    -> CoordinateSystemRemover
CoordinateSystemRemover
    -> FeatureJoiner [LEFT]
    -> AttributeRemover_2
AttributeRemover_2
    REMOVE_ATTRS = input_file_full_path,input_file,input_file_name,input_file_type,fme_type,input_file_full_path_lw,input_file_lw,input_file_name_lw,input_file_type_lw
    -> FeatureMerger_4 [REQUESTOR]
Junction_5
    -> AttributeKeeper
FeatureJoiner
    ATTR_CONFLICT_RES = Prefer Left
    GEOMETRY_HANDLING = Prefer Left
    JOIN_KEYS = fme_feature_type_name fme_feature_type_name AUTO
    JOIN_MODE = Inner
    JOINED -> AttributeRemover
AttributeRemover
    REMOVE_ATTRS = fme_data_type,input_file_full_path,input_file,input_file_name,input_file_type,fme_type,input_file_full_path_lw,input_file_lw,input_file_name_lw,input_file_type_lw,coordsys,geometry_wkt
    -> AttributeDereferencer

Bookmark: Attributter konverteres til XML-tags
AttributeDereferencer
    DEST_ATTR = value
    SRC_ATTR = name
    -> Tester_Null
Tester_Null
    BOOL_OP = OR
    TEST_CLAUSE = TEST value ATTRIBUTE_HAS_A_VALUE ""
    TEST_MODE = TEST
    PASSED -> XMLTemplater_AttrValues [ROOT]
XMLTemplater_AttrValues
    OUTPUT_XML_HEADER = No
    RESULT_ATTRIBUTE = _xml
    ROOT_QUERY_EXPR = <TAG>{fme:get-attribute("value")}</TAG>
    VISIBLE_QUERY_VALIDATE = Yes
    -> StringReplacer
StringReplacer
    CASE = NO
    FIND_TEXT = <(/?)TAG>|<TAG(/)>
    NO_MATCH = _FME_NO_OP_
    REGEXP = YES
    REPLACE_TEXT = <\1@LowerCase(@Value(name))\2>
    SRC_ATTRS = _xml
    -> Sorter
Sorter
    SORT_PARM = _element_index NUMERIC ASCENDING
    SORTED -> Aggregator
Aggregator
    ACCUM_ATTRS_NAME = Drop Incoming Attributes
    COUNT_ATTR = _element_count
    GROUP_BY = fme_feature_type_name fme_feature_type feature_id
    LIST_ATTRS_TO_INCLUDE = _xml
    LIST_NAME = _xml_lst
    MODE = Attributes Only
    SEP = ,
    AGGREGATE -> FeatureMerger_4 [SUPPLIER]

Bookmark: Attributter og geometri samles til XML features
Note: Merge, hvis alle attributter er væk, filtreret eller NULL
FeatureMerger_4
    ATTR_ACCUM_MODE = Merge Supplier
    ATTR_CONFLICT_RES = Use Requestor
    IGNORE_NULLS = No
    JOIN_KEYS = @Value(fme_feature_type_name) @Value(fme_feature_type_name) AUTO @Value(feature_id) @Value(feature_id) AUTO
    MERGE_TYPE = Attributes Only
    PROCESS_DUPS = NO
    REJECT_NULL_MISSING_KEYS = No
    SUPPLIERS_FIRST = No
    MERGED -> XMLTemplater_Feature [ROOT]
    UNMERGED_REQUESTOR -> XMLTemplater_Feature_2 [ROOT]
XMLTemplater_Feature
    OUTPUT_XML_HEADER = No
    RESULT_ATTRIBUTE = _xml
    ROOT_QUERY_EXPR:
      <feature fid="{fme:get-attribute("feature_id")}">
      	<geometry>{fme:get-attribute("geometry_wkt")}</geometry>
          <attributes>
           {
            let $list_size := xs:integer(fme:get-attribute( "_element_count" ) )
            for $i in (0 to $list_size - 1)
               return (fme:get-xml-attribute( concat("_xml_lst{",$i,"}._xml" ) ),"&#xA;    ")
           }
          </attributes>
      </feature>
    VISIBLE_QUERY_VALIDATE = No
    -> Sorter_2
XMLTemplater_Feature_2
    OUTPUT_XML_HEADER = No
    RESULT_ATTRIBUTE = _xml
    ROOT_QUERY_EXPR:
      <feature fid="{fme:get-attribute("feature_id")}">
      	<geometry>{fme:get-attribute("geometry_wkt")}</geometry>
      </feature>
    VISIBLE_QUERY_VALIDATE = No
    -> Sorter_2
Sorter_2
    SORT_PARM = feature_id NUMERIC ASCENDING
    SORTED -> Aggregator_2
Aggregator_2
    ACCUM_ATTRS_NAME = Drop Incoming Attributes
    AGGREGATE_TYPE = Homogeneous Collection (If Possible)
    COUNT_ATTR = _element_count
    GROUP_BY = fme_feature_type_name fme_feature_type
    LIST_ATTRS_TO_INCLUDE = _xml
    LIST_NAME = _xml_lst
    MODE = Geometry - Assemble One Level
    SEP = ,
    AGGREGATE -> BoundsExtractor
BoundsExtractor
    XMAX = _xmax
    XMIN = _xmin
    YMAX = _ymax
    YMIN = _ymin
    -> FeatureMerger_3 [REQUESTOR]

Bookmark: Liste over filens attributter
Sorter_3
    SORT_PARM = _element_index NUMERIC ASCENDING
    SORTED -> AttributeCreator_5
AttributeCreator_5
    ATTR_TABLE = SET_TO name_lw (varchar(200)) = @LowerCase(@Value(name))
    -> DuplicateFilter
DuplicateFilter
    INPUT_ORDERED_CHOICE = No
    KEYATTR = fme_feature_type_name name_lw
    UNIQUE -> XMLTemplater_InputFileAttr [ROOT]
XMLTemplater_InputFileAttr
    OUTPUT_XML_HEADER = No
    RESULT_ATTRIBUTE = _xml
    ROOT_QUERY_EXPR = <attribute name="{fme:get-attribute("name_lw")}"/>
    VISIBLE_QUERY_VALIDATE = Yes
    -> Aggregator_4
Aggregator_4
    ACCUM_ATTRS_NAME = Drop Incoming Attributes
    AGGREGATE_TYPE = Homogeneous Collection (If Possible)
    COUNT_ATTR = _element_count_attr
    GROUP_BY = fme_feature_type_name coordsys coordsys_epsg
    LIST_ATTRS_TO_INCLUDE = _xml
    LIST_NAME = _xml_lst_attr
    MODE = Geometry - Assemble One Level
    SEP = ,
    AGGREGATE -> FeatureMerger [SUPPLIER]

Bookmark: Filer og attributlister samles
FeatureMerger
    ATTR_ACCUM_MODE = Merge Supplier
    ATTR_CONFLICT_RES = Use Requestor
    IGNORE_NULLS = No
    JOIN_KEYS = @Value(fme_feature_type_name) @Value(fme_feature_type_name) AUTO
    MERGE_TYPE = Attributes Only
    PROCESS_DUPS = NO
    REJECT_NULL_MISSING_KEYS = No
    SUPPLIERS_FIRST = No
    MERGED -> AttributeKeeper_2
    UNMERGED_REQUESTOR -> FeatureMerger_6 [REQUESTOR]
FeatureMerger_6
    ATTR_ACCUM_MODE = Merge Supplier
    ATTR_CONFLICT_RES = Use Requestor
    IGNORE_NULLS = No
    JOIN_KEYS = @Value(fme_feature_type_name) @Value(fme_feature_type_name) AUTO
    MERGE_TYPE = Attributes Only
    PROCESS_DUPS = NO
    REJECT_NULL_MISSING_KEYS = No
    SUPPLIERS_FIRST = No
    MERGED -> AttributeKeeper_2
    UNMERGED_REQUESTOR -> AttributeKeeper_2
AttributeKeeper_2
    CREATE_BULK_MODE_FEATURES = NO
    KEEP_ATTRS = fme_feature_type_name,input_file,input_file_type,input_file_name,feature_type_format,_element_count_attr,fme_feature_type,input_file_lw,input_file_name_lw,input_file_type_lw,coordsys,coordsys_epsg
    KEEP_LIST = _xml_lst_attr{}
    -> Sorter_5
Sorter_5
    SORT_PARM = fme_feature_type_name NATURAL ASCENDING
    SORTED -> Counter
Counter
    CNT_ATTR = inputfile_fid
    SCOPE = Local
    START = 1
    -> FeatureMerger_3 [SUPPLIER]

Bookmark: Features samles i respektive filer
FeatureMerger_3
    ATTR_ACCUM_MODE = Merge Supplier
    ATTR_CONFLICT_RES = Use Requestor
    IGNORE_NULLS = No
    JOIN_KEYS = @Value(fme_feature_type_name) @Value(fme_feature_type_name) AUTO
    MERGE_TYPE = Attributes Only
    PROCESS_DUPS = NO
    REJECT_NULL_MISSING_KEYS = No
    SUPPLIERS_FIRST = No
    MERGED -> Tester_4
    MERGED -> Junction_3
    UNUSED_SUPPLIER -> XMLTemplater_InputFile_3 [ROOT]
Tester_4
    BOOL_OP = OR
    TEST_CLAUSE = TEST _element_count_attr ATTRIBUTE_HAS_A_VALUE ""
    TEST_MODE = TEST
    PASSED -> XMLTemplater_InputFile [ROOT]
    FAILED -> XMLTemplater_InputFile_2 [ROOT]
Note: Data med attributter
XMLTemplater_InputFile
    OUTPUT_XML_HEADER = No
    RESULT_ATTRIBUTE = _xml
    ROOT_QUERY_EXPR:
      <inputFile fid="{fme:get-attribute("inputfile_fid")}" id="{fme:get-attribute("fme_feature_type_name")}">
          <file>{fme:get-attribute("input_file")}</file>
          <fileName>{fme:get-attribute("input_file_name")}</fileName>
          <fileExtension>{fme:get-attribute("input_file_type")}</fileExtension>
          <featureType>{fme:get-attribute("fme_feature_type")}</featureType>
          <featureSRID>{fme:get-attribute("coordsys_epsg")}</featureSRID>
          <featureCount>{fme:get-attribute("_element_count")}</featureCount>
          <featureBounds>
              <xmin>{fme:get-attribute("_xmin")}</xmin>
              <ymin>{fme:get-attribute("_ymin")}</ymin>
              <xmax>{fme:get-attribute("_xmax")}</xmax>
              <ymax>{fme:get-attribute("_ymax")}</ymax>
          </featureBounds>
          <attributes>
           {
            let $list_size := xs:integer(fme:get-attribute( "_element_count_attr" ) )
            for $i in (0 to $list_size - 1)
               return (fme:get-xml-attribute( concat("_xml_lst_attr{",$i,"}._xml" ) ),"&#xA;    ")
           }
          </attributes>
          <features>
           {
            let $list_size := xs:integer(fme:get-attribute( "_element_count" ) )
            for $i in (0 to $list_size - 1)
               return (fme:get-xml-attribute( concat("_xml_lst{",$i,"}._xml" ) ),"&#xA;    ")
           }
          </features>
      </inputFile>
    VISIBLE_QUERY_VALIDATE = Yes
    -> Sorter_4
Note: Data uden attributter
XMLTemplater_InputFile_2
    OUTPUT_XML_HEADER = No
    RESULT_ATTRIBUTE = _xml
    ROOT_QUERY_EXPR:
      <inputFile fid="{fme:get-attribute("inputfile_fid")}" id="{fme:get-attribute("fme_feature_type_name")}">
          <file>{fme:get-attribute("input_file")}</file>
          <fileName>{fme:get-attribute("input_file_name")}</fileName>
          <fileExtension>{fme:get-attribute("input_file_type")}</fileExtension>
          <featureType>{fme:get-attribute("fme_feature_type")}</featureType>
          <featureSRID>{fme:get-attribute("coordsys_epsg")}</featureSRID>
          <featureCount>{fme:get-attribute("_element_count")}</featureCount>
          <featureBounds>
              <xmin>{fme:get-attribute("_xmin")}</xmin>
              <ymin>{fme:get-attribute("_ymin")}</ymin>
              <xmax>{fme:get-attribute("_xmax")}</xmax>
              <ymax>{fme:get-attribute("_ymax")}</ymax>
          </featureBounds>
          <features>
           {
            let $list_size := xs:integer(fme:get-attribute( "_element_count" ) )
            for $i in (0 to $list_size - 1)
               return (fme:get-xml-attribute( concat("_xml_lst{",$i,"}._xml" ) ),"&#xA;    ")
           }
          </features>
      </inputFile>
    VISIBLE_QUERY_VALIDATE = Yes
    -> Sorter_4
Junction_3
    -> Reprojector
Note: Ingen data
XMLTemplater_InputFile_3
    OUTPUT_XML_HEADER = No
    RESULT_ATTRIBUTE = _xml
    ROOT_QUERY_EXPR:
      <inputFile fid="{fme:get-attribute("inputfile_fid")}" id="{fme:get-attribute("fme_feature_type_name")}">
          <file>{fme:get-attribute("input_file")}</file>
          <fileName>{fme:get-attribute("input_file_name")}</fileName>
          <fileExtension>{fme:get-attribute("input_file_type")}</fileExtension>
          <featureType>{fme:get-attribute("fme_feature_type")}</featureType>
      </inputFile>
    VISIBLE_QUERY_VALIDATE = Yes
    -> Sorter_4
Sorter_4
    SORT_PARM = inputfile_fid NUMERIC ASCENDING
    SORTED -> Aggregator_3
Aggregator_3
    ACCUM_ATTRS_NAME = Drop Incoming Attributes
    COUNT_ATTR = _element_count
    GROUP_BY = feature_type_format
    LIST_ATTRS_TO_INCLUDE = _xml
    LIST_NAME = _xml_lst
    MODE = Attributes Only
    SEP = ,
    AGGREGATE -> UniqueIdentifierGenerator

Bookmark: Filer samles i en KontrolLER XML
Reprojector
    DEST = EPSG:25832
    INTERPOLATION_TYPE_NAME = Nearest Neighbor
    RASTER_CELL_SIZE = Preserve Cells
    RASTER_TOLERANCE = 0.0
    SOURCE = FME_CONDITIONAL:DEFAULT_VALUE'EPSG:25832'BOOL_OP;OR;COMPOSITE_TEST;1;TEST coordsys ATTRIBUTE_HAS_A_VALUE _FME_BLANK_STRING_'@Value(coordsys)'FME_NUM_CONDITIONS2___
    REPROJECTED -> GeometryFilter_2
GeometryFilter_2
    FILTER_MODE = SIMPLE
    FILTER_MULTI = FILTER_TYPES]Null]FME_CONTROLLER_QUERY_FILE]]FME_CONTROLLER_CHOICE]Simple
    <UNFILTERED> -> Bufferer
Bufferer
    ANGLE = 90
    CAP_STYLE = Arc
    CORNER_STYLE = Arc
    MODE = AREA
    OFFSET = 5
    OFFSET_UNITS = NONE
    PRECISION = APPROX
    BUFFERED -> BoundingBoxAccumulator
BoundingBoxAccumulator
    ACCUM_ATTRS_NAME = Use Attributes From One Feature
    GROUP_BY = fme_feature_type_name
    BOUNDING_BOX -> Dissolver
Dissolver
    ACCUM_INPUT_ATTRS = Drop Incoming Attributes
    CLEANING_TOLERANCE = Automatic
    CONNECT_Z_MODE = First Wins
    DEAGGREGATE_INPUT = Yes
    AREA -> Aggregator_5
Aggregator_5
    ACCUM_ATTRS_NAME = Drop Incoming Attributes
    AGGREGATE_TYPE = Homogeneous Collection (If Possible)
    MODE = Geometry - Assemble One Level
    SEP = ,
    AGGREGATE -> FeatureMerger_7 [SUPPLIER]
UniqueIdentifierGenerator
    UUID_ATTR = guid
    UUID_FORMAT = UUID_ONLY
    -> AttributeCreator_4
AttributeCreator_4
    ATTR_TABLE:
      SET_TO datooprettet (varchar(200)) = @Substring(@DateTimeNow(),0,14)
      SET_TO datooprettet_format (varchar(200)) = @DateTimeFormat(@Value(datooprettet),%Y-%m-%d %H:%M:%S)
      SET_TO titel (varchar(200)) = FME_CONDITIONAL:DEFAULT_VALUE'FME_NULL_VALUE'BOOL_OP;OR;COMPOSITE_TEST;1;TEST @Trim($(title)) != _FME_BLANK_STRING_'$(title)'FME_NUM_CONDITIONS2___
    -> XMLTemplater_KontrolLER [ROOT]
XMLTemplater_KontrolLER
    OUTPUT_XML_HEADER = No
    RESULT_ATTRIBUTE = _xml
    ROOT_QUERY_EXPR:
      <kontrolLER guid="{fme:get-attribute("guid")}" oprettet="{fme:get-attribute("datooprettet_format")}">
          <title>$(title)</title>
          <existingFromDB>$(existingFromDB)</existingFromDB>
          <fileIdFormat>{fme:get-attribute("feature_type_format")}</fileIdFormat>
          <fileCount>{fme:get-attribute("_element_count")}</fileCount>
          <inputFiles>
           {
            let $list_size := xs:integer(fme:get-attribute( "_element_count" ) )
            for $i in (0 to $list_size - 1)
               return (fme:get-xml-attribute( concat("_xml_lst{",$i,"}._xml" ) ),"&#xA;    ")
           }
          </inputFiles>
      </kontrolLER>
    VISIBLE_QUERY_VALIDATE = Yes
    -> AttributeKeeper_3
AttributeKeeper_3
    CREATE_BULK_MODE_FEATURES = NO
    KEEP_ATTRS = datooprettet,guid,_xml,titel
    -> XMLFormatter
XMLFormatter
    COLLAPSE_EMPTY_ELEMENT = Yes
    FORMATTING_CHOICE = Pretty-Print XML
    INDENT_SIZE = 1
    LIST_NAME = _xml_error
    NAMESPACE_CLEANUP = No
    OUTPUT_ENCODING = utf-8
    REMOVE_ALL_COMMENT = No
    REMOVE_EMPTY_ELEMENT = Yes
    REMOVE_XML_HEADER = no
    REPLACE_TABS_WITH_SPACES = no
    SCHEMALOC_CLEANUP = No
    TEXT_INDENT = no
    WHITESPACE_HANDLING = Preserve all whitespace
    XML_ATTR_TEXT = _xml
    XML_INPUT_TYPE = Attribute Specifying XML Text
    XML_OUTPUT_ATTR = _xml
    XML_OUTPUT_TYPE = Attribute
    PASSED -> FeatureMerger_7 [REQUESTOR]
FeatureMerger_7
    JOIN_KEYS = 1 1 AUTO
    MERGE_TYPE = Geometry
    PROCESS_DUPS = NO
    REJECT_NULL_MISSING_KEYS = No
    SUPPLIERS_FIRST = No
    MERGED -> FeatureWriter [Table1]
    UNMERGED_REQUESTOR -> FeatureWriter [Table1]
FeatureWriter
    DATASET = KGBPRODSU
    DATASET_ATTR = _dataset
    FEATURE_TYPE_LIST_ATTR = _feature_types
    FORMAT = POSTGIS
    MORE_SUMMARY_ATTRS = guid
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = KGBPRODSU
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
    SUMMARY -> SQLExecutor_2 [INITIATOR]

Bookmark: Hent rapport
SQLExecutor_2
    COMBINE_ATTRS = Result Attributes Only
    COMBINE_GEOM = Initiator Geometry Only
    DATASET = KGBPRODSU
    EXPOSED_ATTRIBUTE_LIST = html_content
    FORMAT = POSTGRES
    OUTPUT_FEATURES_DISPLAY = Schema and Data Features
    POSTGRES_CREATE_FEATURE_TABLES_FROM_DATA = Yes
    POSTGRES_NAMED_CONNECTION = KGBPRODSU
    POSTGRES_QUERY_FEATURE_TYPES_FOR_MERGE_FILTERS = Yes
    POSTGRES_READ_TIME_WITH_TIMEZONE = Yes
    SQL_STATEMENT:
      SELECT
          _html_rapport AS html_content
      FROM $(kontrolSchema).kontrol_xml
      WHERE guid = '@Value(_feature_types{0}.guid)'
    RESULT -> HTML (writer HTML_1)
HTML (writer HTML_1)
    attributes: html_content buffer

FME custom transformer LookupTester
Test attributdata op mod værdier i en given lookup-tabel

Parameters:
- VAL_ = @Value(val_)   # Val
- NAVN = @Value(navn)   # navn
- FME_FEATURE_TYPE_NAME = @Value(fme_feature_type_name)   # Fme Feature Type Name
- LER_SKAERING = @Value(ler_skaering)   # Ler Skaering
- tooltip_val_pr_column = 15   # Antal pr kolonne (tooltip)
- ler_attr =   # LER-attribut
- nillable =   # Nillable
- ukendt_voidable_foer_skaering =   # Ukendt før skæring (Voidable)
- ukendt_voidable =   # Ukendt (Voidable)
- html_tooltip =   # HTML Tooltip

Creator
    GEOMTYPE = Geometry Object
    NUM = 1
    CREATED -> FeatureMerger_4 [SUPPLIER]
Data (input)
    -> FeatureMerger [REQUESTOR]
LER-attributter (input)
    -> FeatureMerger [SUPPLIER]
FeatureMerger
    ATTR_ACCUM_MODE = Merge Supplier
    ATTR_CONFLICT_RES = Use Requestor
    IGNORE_NULLS = No
    JOIN_KEYS = @Value(fme_feature_type_name) @Value(fme_feature_type_name) AUTO $(ler_attr) @Value(navn) AUTO
    MERGE_TYPE = Attributes Only
    PROCESS_DUPS = NO
    REJECT_NULL_MISSING_KEYS = No
    SUPPLIERS_FIRST = No
    MERGED -> AttributeDereferencer
    USED_SUPPLIER -> Ler-attributter (output)
AttributeDereferencer
    DEST_ATTR = val_
    SRC_ATTR = navn
    -> FeatureMerger_3 [REQUESTOR]
Ler-attributter (output)
Lookup-værdier (input)
    -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Tester_2
    UNUSED_SUPPLIER -> Tester_2
Tester_2
    BOOL_OP = OR
    TEST_CLAUSE:
      TEST @Value(val_) != ukendt
      TEST $(ukendt_voidable_foer_skaering) = YES
      TEST $(ukendt_voidable) = YES
    TEST_MODE = TEST
    PASSED -> Tester_3
    PASSED -> StatisticsCalculator
Tester_3
    BOOL_OP = OR
    TEST_CLAUSE = TEST val_ NOT_ATTRIBUTE_IS_MISSING ""
    TEST_MODE = TEST
    PASSED -> FeatureMerger_2 [SUPPLIER]
StatisticsCalculator
    CALCULATION_MODE = NUMERIC
    FEAT_STATS = val_,NUMERIC_MODE,,,COUNT,,,,,,,,,,
    COMPLETE -> AttributeCreator_3
AttributeCreator_3
    ATTR_TABLE:
      SET_TO val_sort (varchar(200)) = @LowerCase(@Value(val_))
      SET_TO val_ (varchar(200)) = @ReplaceString(@Value(val_),&,&amp;)
      SET_TO val_ (varchar(200)) = @ReplaceString(@Value(val_),>,&gt;)
      SET_TO val_ (varchar(200)) = @ReplaceString(@Value(val_),<,&lt;)
      SET_TO val_ (varchar(200)) = @ReplaceString(@Value(val_),"\"",&quot;)
      SET_TO val_ (varchar(200)) = @ReplaceString(@Value(val_),',&apos;)
      SET_TO html_tooltip (varchar(200)) = FME_CONDITIONAL:DEFAULT_VALUE'_FME_NO_OP_'BOOL_OP;OR;COMPOSITE_TEST;1;TEST @Value(val_) = ukendt'			<br>
        			<li>@Value(val_)</li>'BOOL_OP;OR;COMPOSITE_TEST;1;TEST val_ ATTRIBUTE_HAS_A_VALUE _FME_BLANK_STRING_'			<li>@Value(val_)</li>'FME_NUM_CONDITIONS3___
      SET_TO order_ (varchar(200)) = FME_CONDITIONAL:DEFAULT_VALUE'0'BOOL_OP;OR;COMPOSITE_TEST;1;TEST @Value(val_) = ukendt'2'BOOL_OP;OR;COMPOSITE_TEST;1;CASE_INSENSITIVE_TEST @Value(val_) BEGINS_WITH other: '1'FME_NUM_CONDITIONS3___
      SET_TO val_columns (varchar(200)) = FME_CONDITIONAL:DEFAULT_VALUE'_FME_NO_OP_'BOOL_OP;OR;COMPOSITE_TEST;1;TEST $(tooltip_val_pr_column) NOT_= _FME_BLANK_STRING_'@Evaluate(@ceil(@Value(val_.total_count) / $(tooltip_val_pr_column),0))'FME_NUM_CONDITIONS2___
    -> Sorter
Sorter
    SORT_PARM = order_ NUMERIC ASCENDING val_sort ALPHA ASCENDING
    SORTED -> Aggregator
Aggregator
    ACCUM_ATTRS_NAME = Drop Incoming Attributes
    AGGREGATE_TYPE = Homogeneous Collection (If Possible)
    CONCAT_ATTRS = html_tooltip
    GROUP_BY = val_columns
    MODE = Geometry - Assemble One Level
    SEP = "\n"
    AGGREGATE -> AttributeCreator_4
AttributeCreator_4
    ATTR_TABLE:
      SET_TO html_tooltip (varchar(200)) = FME_CONDITIONAL:DEFAULT_VALUE'_FME_NO_OP_'BOOL_OP;AND;COMPOSITE_TEST;1 AND 2 AND 3;TEST val_columns ATTRIBUTE_HAS_A_VALUE _FME_BLANK_STRING_;NUM_TEST @Value(val_columns) > 1;TEST html_tooltip NOT_ATTRIBUTE_IS_EMPTY _FME_BLANK_STRING_'		<ul class="ul-columns" style="columns: @Value(val_columns); -webkit-columns: @Value(val_columns); -moz-columns: @Value(val_columns);">
        @Value(html_tooltip)
        		</ul>'BOOL_OP;OR;COMPOSITE_TEST;1;TEST html_tooltip NOT_ATTRIBUTE_IS_EMPTY _FME_BLANK_STRING_'		<ul>
        @Value(html_tooltip)
        		</ul>'FME_NUM_CONDITIONS3___
      SET_TO html_tooltip (varchar(200)) = FME_CONDITIONAL:DEFAULT_VALUE'FME_NULL_VALUE'BOOL_OP;AND;COMPOSITE_TEST;1 AND 2;TEST $(ukendt_voidable_foer_skaering) = YES;TEST html_tooltip NOT_ATTRIBUTE_IS_EMPTY _FME_BLANK_STRING_'		<b>Tilladte værdier<br>(ukendt kun før skæringsdato):</b>
        @Value(html_tooltip)'BOOL_OP;COMPOSITE;COMPOSITE_TEST;1 AND 2;TEST $(nillable) = YES;TEST html_tooltip NOT_ATTRIBUTE_IS_EMPTY _FME_BLANK_STRING_'		<b>Tilladte værdier (NULL tilladt):</b>
        @Value(html_tooltip)'BOOL_OP;AND;COMPOSITE_TEST;1 AND 2;TEST $(nillable) = YES;TEST html_tooltip ATTRIBUTE_IS_EMPTY _FME_BLANK_STRING_'		<b>NULL tilladt</b>'BOOL_OP;OR;COMPOSITE_TEST;1;TEST html_tooltip NOT_ATTRIBUTE_IS_EMPTY _FME_BLANK_STRING_'		<b>Tilladte værdier:</b>
        @Value(html_tooltip)'FME_NUM_CONDITIONS5___
      SET_TO html_tooltip (buffer) = FME_CONDITIONAL:DEFAULT_VALUE'_FME_NO_OP_'BOOL_OP;OR;COMPOSITE_TEST;1;TEST $(html_tooltip) NOT_= _FME_BLANK_STRING_'@Value(html_tooltip)
                <hr class="tooltip_break">
        $(html_tooltip)'FME_NUM_CONDITIONS2___
    -> FeatureMerger_3 [SUPPLIER]
FeatureMerger_3
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureMerger_2 [REQUESTOR]
    UNMERGED_REQUESTOR -> FeatureMerger_2 [REQUESTOR]
FeatureMerger_2
    ATTR_ACCUM_MODE = Merge Supplier
    ATTR_CONFLICT_RES = Use Requestor
    IGNORE_NULLS = No
    JOIN_KEYS = @Value(val_) @Value(val_) AUTO
    MERGE_TYPE = Attributes Only
    PROCESS_DUPS = NO
    REJECT_NULL_MISSING_KEYS = No
    SUPPLIERS_FIRST = No
    MERGED -> Tester
    UNMERGED_REQUESTOR -> AttributeCreator_2
Tester
    BOOL_OP = COMPOSITE
    COMPOSITE_TEST:
      1 OR ( 2 AND 3 )
       OR 4
    TEST_CLAUSE:
      TEST @Value(val_) != ukendt
      TEST @Value(ler_skaering) = 0
      TEST $(ukendt_voidable_foer_skaering) = YES
      TEST $(ukendt_voidable) = YES
    TEST_MODE = TEST
    PASSED -> AttributeCreator
    FAILED -> AttributeCreator_2
AttributeCreator
    ATTR_TABLE = SET_TO fejl (uint64) = 0
    -> Merged (output)
Merged (output)
AttributeCreator_2
    ATTR_TABLE = SET_TO fejl (uint64) = FME_CONDITIONAL:DEFAULT_VALUE'1'BOOL_OP;AND;COMPOSITE_TEST;1 AND 2;TEST $(nillable) = YES;TEST val_ ATTRIBUTE_VALUE_NULL _FME_BLANK_STRING_'0'FME_NUM_CONDITIONS2___
    -> Unmerged (output)
Unmerged (output)

FME custom transformer GeometryMetadata
Oprete metadata på geometier. Koter og længder til kontrol

Parameters:
- JS_ID = @Value(js_id)   # Js Id
- JS_ID_COUNT = @Value(js_id_count)   # Js Id Count
- TYPE = @Value(type)   # type
- LER_SKAERING = @Value(ler_skaering)   # Ler Skaering
- FME_GEOMETRY = @Value(fme_geometry)   # Fme Geometry

Input (input)
    -> CoordinateExtractor
    -> PartCounter
    -> Tester
Tester
    BOOL_OP = OR
    TEST_CLAUSE = TEST @Value(type) = ledning
    TEST_MODE = TEST
    PASSED -> Reprojector
Reprojector
    DEST = EPSG:25832
    INTERPOLATION_TYPE_NAME = Nearest Neighbor
    RASTER_CELL_SIZE = Preserve Cells
    RASTER_TOLERANCE = 0.0
    REPROJECTED -> Chopper
    REPROJECTED -> LengthCalculator
Chopper
    DEAGGREGATE_INPUT = Deaggregate
    MAX_VERTICES = 2
    MODE = By Vertex
    REMNANT_ATTR = _remnant
    CHOPPED -> LengthCalculatorKnude
    UNTOUCHED -> LengthCalculatorKnude
LengthCalculatorKnude
    DIM = 2
    LEN_ATTR = knude_length_limit
    MULT = 1
    -> Tester_2
Tester_2
    BOOL_OP = OR
    TEST_CLAUSE = TEST @Value(knude_length_limit) > 25
    TEST_MODE = TEST
    PASSED -> StatisticsCalculator_2
    PASSED -> StatisticsCalculator_4
    FAILED -> StatisticsCalculator_4
StatisticsCalculator_4
    CALCULATION_MODE = NUMERIC
    FEAT_STATS = knude_length_limit,NUMERIC_MODE,MIN,MAX,,,,,,,,,,,
    GROUP_BY = js_id js_id_count
    SUMMARY -> AttributeManager
AttributeManager
    ATTR_TABLE:
      RENAME_SET_VALUE knude_length_limit.min > knude_length.min (real64)
      RENAME_SET_VALUE knude_length_limit.max > knude_length.max (real64)
    -> FeatureMerger_4 [REQUESTOR]
StatisticsCalculator_2
    CALCULATION_MODE = NUMERIC
    FEAT_STATS = knude_length_limit,NUMERIC_MODE,MIN,MAX,,,,,,,,,,,
    GROUP_BY = js_id js_id_count
    SUMMARY -> FeatureMerger_2 [SUPPLIER]
LengthCalculator
    DIM = 2
    LEN_ATTR = length
    MULT = 1
    -> FeatureMerger_4 [SUPPLIER]
FeatureMerger_4
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> FeatureMerger_2 [REQUESTOR]
    UNMERGED_REQUESTOR -> FeatureMerger_2 [REQUESTOR]
FeatureMerger_2
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> FeatureMergerLength [SUPPLIER]
    UNMERGED_REQUESTOR -> FeatureMergerLength [SUPPLIER]
Note: Knudepunkter og længder
PartCounter
    COUNT_ATTR = _part_count
    RECURSIVE_PARAM = No
    -> GeometryValidator
GeometryValidator
    ISSUE_ATTR_NAME = _issues
    PRESETS = OGC
    REPAIR = No
    RULES = OGC_VALID_CHECK OGC_VERSION]V1.2.0]LEGACY_OGC]No]FME_CONTROLLER_QUERY_FILE]transformers/dependencies/geometryvalidator8/OGC_VALID_CHECK.fme]FME_CONTROLLER_CHOICE]OGC_VALID_CHECK OGC_SIMPLE_CHECK LEGACY_OGC]No]FME_CONTROLLER_QUERY_FILE]transformers/dependencies/geometryvalidator8/OGC_SIMPLE_CHECK.fme]FME_CONTROLLER_CHOICE]OGC_SIMPLE_CHECK
    SUMMARY = Brief
    PASSED -> AttributeCreator_2
    FAILED -> ListElementCounter
AttributeCreator_2
    ATTR_TABLE = SET_TO _issues_count (uint64) = 0
    -> FeatureMergerZ [REQUESTOR]
ListElementCounter
    CNT_ATTR = _issues_count
    LIST_NAME = _issues{}
    -> AttributeRemover
AttributeRemover
    LIST_ATTRS = _issues{}
    -> FeatureMergerZ [REQUESTOR]
Note: Z koordinater
CoordinateExtractor
    LIST_NAME = _indices
    MODE = All Coordinates
    -> ListElementCounter_2
ListElementCounter_2
    CNT_ATTR = _element_count
    LIST_NAME = _indices{}
    -> Tester_3
Tester_3
    BOOL_OP = OR
    TEST_CLAUSE = NUM_TEST @Value(_element_count) > 0
    TEST_MODE = NUM_TEST
    PASSED -> AttributeRemover_2
AttributeRemover_2
    REMOVE_ATTRS = _element_count
    -> ListExploder
ListExploder
    ATTR_ACCUM_MODE = Merge List Attributes
    ATTR_CONFLICT_RES = Use List Attribute Values
    INDEX_ATTR = _element_index
    LIST_ATTR = _indices{}
    ELEMENTS -> TestFilter
    ELEMENTS -> StatisticsCalculator
StatisticsCalculator
    CALCULATION_MODE = NUMERIC
    FEAT_STATS = z,NUMERIC_MODE,,,COUNT,,,,,,,,,,
    GROUP_BY = js_id js_id_count
    SUMMARY -> FeatureMerger_0 [REQUESTOR]
TestFilter
    DEFAULT_VALUE = <UNFILTERED>
    PASSED_TEST_GROUP_OUTPUT = FIRST
    TEST_LIST = "BOOL_OP,OR,COMPOSITE_TEST,""""""1"""""",TEST_CLAUSE,NUM_TEST @Value(z) = 0",0,"BOOL_OP,OR,COMPOSITE_TEST,""""""1"""""",TEST_CLAUSE,NUM_TEST @Value(z) = -99",-99
    0 -> StatisticsCalculator_0
    0 -> StatisticsCalculator_3
    -99 -> StatisticsCalculator_99
    <UNFILTERED> -> StatisticsCalculator_3
StatisticsCalculator_0
    CALCULATION_MODE = NUMERIC
    FEAT_STATS = z,NUMERIC_MODE,,,COUNT,,,,,,,,,,
    GROUP_BY = js_id js_id_count
    SUMMARY -> AttributeCreator_0
AttributeCreator_0
    ATTR_TABLE = SET_TO z.0.total_count (uint64) = @Value(z.total_count)
    -> FeatureMerger_0 [SUPPLIER]
FeatureMerger_0
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> FeatureMerger_99 [REQUESTOR]
    UNMERGED_REQUESTOR -> FeatureMerger_99 [REQUESTOR]
StatisticsCalculator_99
    CALCULATION_MODE = NUMERIC
    FEAT_STATS = z,NUMERIC_MODE,,,COUNT,,,,,,,,,,
    GROUP_BY = js_id js_id_count
    SUMMARY -> AttributeCreator_99
AttributeCreator_99
    ATTR_TABLE = SET_TO z.99.total_count (uint64) = @Value(z.total_count)
    -> FeatureMerger_99 [SUPPLIER]
FeatureMerger_99
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> FeatureMerger_3 [REQUESTOR]
    UNMERGED_REQUESTOR -> FeatureMerger_3 [REQUESTOR]
StatisticsCalculator_3
    CALCULATION_MODE = NUMERIC
    FEAT_STATS = z,NUMERIC_MODE,MIN,MAX,,,,,,,,,,,
    GROUP_BY = js_id js_id_count
    SUMMARY -> FeatureMerger_3 [SUPPLIER]
FeatureMerger_3
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> Junction
    UNMERGED_REQUESTOR -> Junction
Junction
    -> FeatureMergerZ [SUPPLIER]
FeatureMergerZ
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> FeatureMergerLength [REQUESTOR]
    UNMERGED_REQUESTOR -> FeatureMergerLength [REQUESTOR]
FeatureMergerLength
    ATTR_ACCUM_MODE = Merge Supplier
    ATTR_CONFLICT_RES = Use Requestor
    IGNORE_NULLS = No
    JOIN_KEYS = @Value(js_id) @Value(js_id) AUTO @Value(js_id_count) @Value(js_id_count) AUTO
    MERGE_TYPE = Attributes Only
    PROCESS_DUPS = NO
    REJECT_NULL_MISSING_KEYS = No
    SUPPLIERS_FIRST = No
    MERGED -> Junction_2
    UNMERGED_REQUESTOR -> Junction_2
Junction_2
    -> CoordinateSystemExtractor
CoordinateSystemExtractor
    CRDSYS_ATTR = _coordsys
    -> CoordinateSystemDescriptionConverter
CoordinateSystemDescriptionConverter
    DIRECTION_LONG = Convert From FME Representation
    KIND_LONG = EPSG Number
    SRC = _coordsys
    VAL_ATTR = _coordsys
    -> DimensionExtractor
DimensionExtractor
    DIM_ATTR = _dimension
    -> AttributeCreator
AttributeCreator
    ATTR_TABLE:
      SET_TO _coordsys_pretty (varchar(200)) = FME_CONDITIONAL:DEFAULT_VALUE'_FME_NO_OP_'BOOL_OP;OR;COMPOSITE_TEST;1;TEST _coordsys ATTRIBUTE_HAS_A_VALUE _FME_BLANK_STRING_'EPSG:@Value(_coordsys)'FME_NUM_CONDITIONS2___
      SET_TO z.min.max (varchar(200)) = FME_CONDITIONAL:DEFAULT_VALUE'_FME_NO_OP_'BOOL_OP;AND;COMPOSITE_TEST;1 AND 2;TEST z.min ATTRIBUTE_HAS_A_VALUE _FME_BLANK_STRING_;TEST @Value(z.min) = @Value(z.max)'@round(@Value(z.min), 4)'BOOL_OP;OR;COMPOSITE_TEST;1;TEST z.min ATTRIBUTE_HAS_A_VALUE _FME_BLANK_STRING_'@round(@Value(z.min), 4) - @round(@Value(z.max), 4)'FME_NUM_CONDITIONS3___
      SET_TO length_pretty (varchar(200)) = @round(@Value(length), 1)
      SET_TO _coordsys.fejl (varchar(200)) = FME_CONDITIONAL:DEFAULT_VALUE'1'BOOL_OP;OR;COMPOSITE_TEST;1;TEST @Value(_coordsys) IN 4095,4099,25832'0'FME_NUM_CONDITIONS2___
      SET_TO _dimension.fejl (varchar(200)) = FME_CONDITIONAL:DEFAULT_VALUE'1'BOOL_OP;OR;COMPOSITE_TEST;1;TEST @Value(_dimension) = 3'0'FME_NUM_CONDITIONS2___
      SET_TO _issues_count_pretty (varchar(200)) = FME_CONDITIONAL:DEFAULT_VALUE'@Value(_issues_count)'BOOL_OP;OR;COMPOSITE_TEST;1;TEST @Value(_issues_count) = 0'Ingen geometrifejl'FME_NUM_CONDITIONS2___
      SET_TO _issues_count.fejl (varchar(200)) = FME_CONDITIONAL:DEFAULT_VALUE'1'BOOL_OP;OR;COMPOSITE_TEST;1;TEST @Value(_issues_count) = 0'0'FME_NUM_CONDITIONS2___
      SET_TO z.99.total_count.fejl (varchar(200)) = FME_CONDITIONAL:DEFAULT_VALUE'0'BOOL_OP;AND;COMPOSITE_TEST;1 AND 2;TEST @Value(ler_skaering) = 1;TEST z.99.total_count ATTRIBUTE_HAS_A_VALUE _FME_BLANK_STRING_'1'BOOL_OP;OR;COMPOSITE_TEST;1;TEST z.99.total_count ATTRIBUTE_HAS_A_VALUE _FME_BLANK_STRING_'_FME_NO_OP_'FME_NUM_CONDITIONS3___
      SET_TO z.0.total_count.fejl (varchar(200)) = FME_CONDITIONAL:DEFAULT_VALUE'0'BOOL_OP;OR;COMPOSITE_TEST;1;TEST z.0.total_count ATTRIBUTE_HAS_A_VALUE _FME_BLANK_STRING_'_FME_NO_OP_'FME_NUM_CONDITIONS2___
      SET_TO _part_count_pretty (varchar(200)) = FME_CONDITIONAL:DEFAULT_VALUE'Ja'BOOL_OP;AND;COMPOSITE_TEST;1;TEST @Value(_part_count) NOT_= 1'Nej'FME_NUM_CONDITIONS2___
      SET_TO _part_count.fejl (varchar(200)) = FME_CONDITIONAL:DEFAULT_VALUE'0'BOOL_OP;AND;COMPOSITE_TEST;1;TEST @Value(_part_count) NOT_= 1'1'FME_NUM_CONDITIONS2___
      SET_TO knude_length_limit.fejl (varchar(200)) = FME_CONDITIONAL:DEFAULT_VALUE'0'BOOL_OP;AND;COMPOSITE_TEST;1 AND 2;TEST @Value(type) = ledning;TEST knude_length_limit.min ATTRIBUTE_HAS_A_VALUE _FME_BLANK_STRING_'1'FME_NUM_CONDITIONS2___
      SET_TO _geom_null.fejl (varchar(200)) = FME_CONDITIONAL:DEFAULT_VALUE'1'BOOL_OP;OR;COMPOSITE_TEST;1;TEST @Value(fme_geometry) NOT_= fme_undefined'0'FME_NUM_CONDITIONS2___
      SET_TO _geom_null_pretty (varchar(200)) = FME_CONDITIONAL:DEFAULT_VALUE'Ingen geometri'BOOL_OP;OR;COMPOSITE_TEST;1;TEST @Value(_geom_null.fejl) = 0'Indeholder geometri'FME_NUM_CONDITIONS2___
    -> Output (output)
Output (output)

FME custom transformer ColumnSubSection

Parameters:
- subsection_title =   # Titel
- sub_section_order =   # Rækkefølge
- TYPE = @Value(type)   # type

Input (input)
    -> AttributeCreator
AttributeCreator
    ATTR_TABLE:
      SET_TO sub_section_title (varchar(200)) = @FullTitleCase(@Value(type)): $(subsection_title)
      SET_TO sub_section_order (varchar(200)) = $(sub_section_order)
    -> Output (output)
Output (output)

FME custom transformer TableToolTip
Opret tooltip til tabeller

Parameters:
- HTML_TOOLTIP = @Value(html_tooltip)   # Html Tooltip
- HTML_CONTENT = @Value(html_content)   # Html Content
- html_tooltip_text =   # Tooltip text (No attribute)
- table_class =   # Class på table

Input (input)
    -> Tester
Tester
    BOOL_OP = OR
    TEST_CLAUSE:
      TEST html_tooltip ATTRIBUTE_HAS_A_VALUE ""
      TEST $(html_tooltip_text) != ""
    TEST_MODE = TEST
    PASSED -> AttributeCreator
    FAILED -> AttributeCreator_2
AttributeCreator
    ATTR_TABLE:
      SET_TO html_tooltip (buffer) = FME_CONDITIONAL:DEFAULT_VALUE'_FME_NO_OP_'BOOL_OP;OR;COMPOSITE_TEST;1;TEST html_tooltip NOT_ATTRIBUTE_HAS_A_VALUE _FME_BLANK_STRING_'$(html_tooltip_text)'FME_NUM_CONDITIONS2___
      SET_TO html_tooltip (buffer) = <div class="tabletooltip">
        	?
        	<span class="tooltiptext">
        		@Value(html_tooltip)
        	</span>
        </div>
      SET_TO html_content (buffer) = FME_CONDITIONAL:DEFAULT_VALUE'_FME_NO_OP_'BOOL_OP;OR;COMPOSITE_TEST;1;TEST html_tooltip ATTRIBUTE_HAS_A_VALUE _FME_BLANK_STRING_'@ReplaceRegularExpression(@Value(html_content),(<thead>.+?)<th></th>,\1<th>@Value(html_tooltip)</th>)'FME_NUM_CONDITIONS2___
      SET_TO html_content (buffer) = FME_CONDITIONAL:DEFAULT_VALUE'_FME_NO_OP_'BOOL_OP;OR;COMPOSITE_TEST;1;TEST $(table_class) != _FME_BLANK_STRING_'@ReplaceString(@Value(html_content),"<table class=\"","<table class=\"$(table_class) ")'FME_NUM_CONDITIONS2___
    -> Output (output)
AttributeCreator_2
    ATTR_TABLE = SET_TO html_content (buffer) = FME_CONDITIONAL:DEFAULT_VALUE'_FME_NO_OP_'BOOL_OP;OR;COMPOSITE_TEST;1;TEST $(table_class) != _FME_BLANK_STRING_'@ReplaceString(@Value(html_content),"<table class=\"","<table class=\"$(table_class) ")'FME_NUM_CONDITIONS2___
    -> Output (output)
Output (output)

FME custom transformer FejlListType

Parameters:
- order_ = 0   # Rækkefølge
- navn =   # Navn
- html_tooltip =   # HTML Tooltip
- VAL_ = @Value(val_)   # Val

Input (input)
    -> AttributeCreator
AttributeCreator
    ATTR_TABLE:
      SET_TO fejl (uint64) = 0
      SET_TO val_ (buffer) = FME_CONDITIONAL:DEFAULT_VALUE''BOOL_OP;OR;COMPOSITE_TEST;1;TEST val_ ATTRIBUTE_HAS_A_VALUE _FME_BLANK_STRING_'@Value(val_)'FME_NUM_CONDITIONS2___
    -> AttributeCreator_3
Input_med_fejl (input)
    -> AttributeCreator_2
AttributeCreator_2
    ATTR_TABLE:
      SET_TO fejl (uint64) = 1
      SET_TO val_ (buffer) = FME_CONDITIONAL:DEFAULT_VALUE'$(navn)'BOOL_OP;OR;COMPOSITE_TEST;1;TEST val_ ATTRIBUTE_HAS_A_VALUE _FME_BLANK_STRING_'@Value(val_)'FME_NUM_CONDITIONS2___
    -> AttributeCreator_3
Input_med_obs (input)
    -> AttributeCreator_4
AttributeCreator_4
    ATTR_TABLE:
      SET_TO fejl (uint64)
      SET_TO val_ (buffer) = FME_CONDITIONAL:DEFAULT_VALUE'$(navn)'BOOL_OP;OR;COMPOSITE_TEST;1;TEST val_ ATTRIBUTE_HAS_A_VALUE _FME_BLANK_STRING_'@Value(val_)'FME_NUM_CONDITIONS2___
    -> AttributeCreator_3
AttributeCreator_3
    ATTR_TABLE:
      SET_TO order_ (varchar(200)) = $(order_)
      SET_TO navn (varchar(200)) = $(navn)
      SET_TO html_tooltip (varchar(200)) = $(html_tooltip)
    -> Output (output)
Output (output)
